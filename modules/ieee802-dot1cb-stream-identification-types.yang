module ieee802-dot1cb-stream-identification-types {
  yang-version "1.1";
  namespace
    urn:ieee:std:802.1Q:yang:ieee802-dot1cb-stream-identification-types;
  prefix dot1cb-sid-types;
  organization
    "Institute of Electrical and Electronics Engineers";
  contact
    "WG-URL: http://ieee802.org/1/
     WG-EMail: stds-802-1-l@ieee.org
    
     Contact: IEEE 802.1 Working Group Chair
              Postal: C/O IEEE 802.1 Working Group
              IEEE Standards Association
              445 Hoes Lane
              Piscataway, NJ 08854
              USA
    
     E-mail: stds-802-1-chairs@ieee.org";
  description
    "Management objects that control the stream identification from IEEE
    Std 802.1CB-2017. This YANG data model conforms to the Network
    Management Datastore Architecture defined in RFC 8342.";
  revision 2020-11-27 {
    description
      "D1.0 revision. Note that this module might change in backward
      incompatible ways until approved as a standard.";
    reference
      "Clause 10 of IEEE Std 802.1CB-2017";
  }
  revision 2020-08-05 {
    description
      "D0.4 revision. Note that this module might change in backward
      incompatible ways until approved as a standard.";
    reference
      "Clause 9 of IEEE Std 802.1CB-2017";
  }
  revision 2020-04-29 {
    description
      "D0.3 revision. Note that this module might change in backward
      incompatible ways until approved as a standard.";
    reference
      "Clause 10 of IEEE Std 802.1CB-2017";
  }
  revision 2019-09-01 {
    description
      "Initial revision. Note that this module might change in backward
      incompatible ways until approved as a standard.";
    reference
      "Clause 9 of IEEE Std 802.1CB-2017";
  }
  typedef direction {
    type boolean;
    description
      "A boolean object indicating whether the direction is out-facing
      (True) or in-facing (False).";
    reference
      "Clause 10.4.1.3 of IEEE Std 802.1CB-2017";
  }
}
